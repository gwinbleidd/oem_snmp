ORACLE-ENTERPRISE-MANAGER-4-MIB DEFINITIONS ::= BEGIN

IMPORTS
	TRAP-TYPE
		FROM RFC-1215
	DisplayString
		FROM RFC1213-MIB
	OBJECT-TYPE
		FROM RFC-1212
	enterprises
		FROM RFC1155-SMI;

oracle OBJECT IDENTIFIER ::= { enterprises  111 }

oraEM4 OBJECT IDENTIFIER ::= { oracle  15 }

oraEM4Traps OBJECT IDENTIFIER ::= { oraEM4  2 }

oraEMNGObjects OBJECT IDENTIFIER ::= { oraEM4  3 }

oraEMNGEventTable OBJECT-TYPE
    SYNTAX  SEQUENCE OF OraEMNGEventEntry
    ACCESS  not-accessible
    STATUS  mandatory
    DESCRIPTION
     "Information on events published to Oracle Enterprise Manager. This table is not queryable; it exists only to document the variables included in the oraEMNGEventTrap trap.  Each trap can contain a single instance of each variable in the table."
    ::= { oraEMNGObjects  1 }

oraEMNGEventEntry OBJECT-TYPE
    SYNTAX  OraEMNGEventEntry
    ACCESS  not-accessible
    STATUS  mandatory
    DESCRIPTION
     "Information about a particular Oracle Enterprise Manager event."
    INDEX   { oraEMNGEventIndex }
    ::= { oraEMNGEventTable  1 }

OraEMNGEventEntry ::=
    SEQUENCE {
        oraEMNGEventIndex
            INTEGER,

        oraEMNGEventNotifType
            DisplayString,

        oraEMNGEventMessage
            DisplayString,

        oraEMNGEventMessageURL
            DisplayString,

        oraEMNGEventSeverity
            DisplayString,

        oraEMNGEventSeverityCode
            DisplayString,

        oraEMNGEventRepeatCount
            DisplayString,

        oraEMNGEventActionMsg
            DisplayString,

        oraEMNGEventOccurrenceTime
            DisplayString,

        oraEMNGEventReportedTime
            DisplayString,

        oraEMNGEventCategories
            DisplayString,

        oraEMNGEventCategoryCodes
            DisplayString,

        oraEMNGEventType
            DisplayString,

        oraEMNGEventName
            DisplayString,

        oraEMNGAssocIncidentId
            DisplayString,

        oraEMNGAssocIncidentOwner
            DisplayString,

        oraEMNGAssocIncidentAcked
            DisplayString,

        oraEMNGAssocIncidentStatus
            DisplayString,

        oraEMNGAssocIncidentPriority
            DisplayString,

        oraEMNGAssocIncidentEscLevel
            DisplayString,

        oraEMNGEventTargetName
            DisplayString,

        oraEMNGEventTargetNameURL
            DisplayString,

        oraEMNGEventTargetType
            DisplayString,

        oraEMNGEventHostName
            DisplayString,

        oraEMNGEventTargetOwner
            DisplayString,

        oraEMNGEventTgtLifeCycleStatus
            DisplayString,

        oraEMNGEventTargetVersion
            DisplayString,

        oraEMNGEventUserDefinedTgtProp
            DisplayString,

        oraEMNGEventSourceObjName
            DisplayString,

        oraEMNGEventSourceObjNameURL
            DisplayString,

        oraEMNGEventSourceObjType
            DisplayString,

        oraEMNGEventSourceObjSubType
            DisplayString,

        oraEMNGEventSourceObjOwner
            DisplayString,

        oraEMNGEventCAJobName
            DisplayString,

        oraEMNGEventCAJobStatus
            DisplayString,

        oraEMNGEventCAJobOwner
            DisplayString,

        oraEMNGEventCAJobStepOutput
            DisplayString,

        oraEMNGEventCAJobType
            DisplayString,

        oraEMNGEventRuleSetName
            DisplayString,

        oraEMNGEventRuleName
            DisplayString,

        oraEMNGEventRuleOwner
            DisplayString,

        oraEMNGEventSequenceId
            DisplayString,

        oraEMNGEventRCADetails
            DisplayString,

        oraEMNGEventContextAttrs
            DisplayString,

        oraEMNGEventUserComments
            DisplayString,

        oraEMNGEventUpdates
            DisplayString,

        oraEMNGEventTotalOccurrenceCount
            DisplayString,

        oraEMNGEventCurrOccurrenceCount
            DisplayString,

        oraEMNGEventCurrFirstOccurDate
            DisplayString,

        oraEMNGEventCurrLastOccurDate
            DisplayString,

        oraEMNGEventRCAStatus
            DisplayString,

        oraEMNGEventReportedState
            DisplayString,

        oraEMNGEventTypeAttr1
            DisplayString,

        oraEMNGEventTypeAttr2
            DisplayString,

        oraEMNGEventTypeAttr3
            DisplayString,

        oraEMNGEventTypeAttr4
            DisplayString,

        oraEMNGEventTypeAttr5
            DisplayString,

        oraEMNGEventTypeAttr6
            DisplayString,

        oraEMNGEventTypeAttr7
            DisplayString,

        oraEMNGEventTypeAttr8
            DisplayString,

        oraEMNGEventTypeAttr9
            DisplayString,

        oraEMNGEventTypeAttr10
            DisplayString,

        oraEMNGEventTypeAttr11
            DisplayString,

        oraEMNGEventTypeAttr12
            DisplayString,

        oraEMNGEventTypeAttr13
            DisplayString,

        oraEMNGEventTypeAttr14
            DisplayString,

        oraEMNGEventTypeAttr15
            DisplayString,

        oraEMNGEventTypeAttr16
            DisplayString,

        oraEMNGEventTypeAttr17
            DisplayString,

        oraEMNGEventTypeAttr18
            DisplayString,

        oraEMNGEventTypeAttr19
            DisplayString,

        oraEMNGEventTypeAttr20
            DisplayString,

        oraEMNGEventTypeAttr21
            DisplayString,

        oraEMNGEventTypeAttr22
            DisplayString,

        oraEMNGEventTypeAttr23
            DisplayString,

        oraEMNGEventTypeAttr24
            DisplayString,

        oraEMNGEventTypeAttr25
            DisplayString
  }

oraEMNGEventIndex OBJECT-TYPE
    SYNTAX INTEGER (0..2147483647)
    ACCESS  read-only
    STATUS  mandatory
    DESCRIPTION
     "Index of a particular event, unique only at the moment an event is generated."
    ::= { oraEMNGEventEntry  1 }

oraEMNGEventNotifType  OBJECT-TYPE
    SYNTAX DisplayString
    ACCESS  read-only
    STATUS  mandatory
    DESCRIPTION
      "Notification Type. NOTIF_NORMAL, NOTIF_RETRY, NOTIF_DURATION, NOTIF_REPEAT, NOTIF_CA, NOTIF_RCA"
    ::= { oraEMNGEventEntry  2 }

oraEMNGEventMessage  OBJECT-TYPE
    SYNTAX DisplayString
    ACCESS  read-only
    STATUS  mandatory
    DESCRIPTION
     "The message associated with this event."
    ::= { oraEMNGEventEntry  3 }

oraEMNGEventMessageURL  OBJECT-TYPE
    SYNTAX DisplayString
    ACCESS  read-only
    STATUS  mandatory
    DESCRIPTION
     "EM Console URL for the event message. Populated for events with severity other than INFORMATIONAL. Empty if trap size exceeds configured snmp packet size."
    ::= { oraEMNGEventEntry  4 }

oraEMNGEventSeverity  OBJECT-TYPE
    SYNTAX DisplayString
    ACCESS  read-only
    STATUS  mandatory
    DESCRIPTION
     "The severity of the event e.g. Fatal, Critical, Warning, Advisory, Information, Clear."
    ::= { oraEMNGEventEntry  5 }

oraEMNGEventSeverityCode  OBJECT-TYPE
    SYNTAX DisplayString
    ACCESS  read-only
    STATUS  mandatory
    DESCRIPTION
     "Internal code of the severity: FATAL, CRITICAL, WARNING, ADVISORY, INFORMATIONAL, CLEAR."
    ::= { oraEMNGEventEntry  6 }

oraEMNGEventRepeatCount  OBJECT-TYPE
    SYNTAX DisplayString
    ACCESS  read-only
    STATUS  mandatory
    DESCRIPTION
     "The repeat notification counter for the event."
    ::= { oraEMNGEventEntry  7 }

oraEMNGEventActionMsg  OBJECT-TYPE
    SYNTAX DisplayString
    ACCESS  read-only
    STATUS  mandatory
    DESCRIPTION
     "The action message for this event."
    ::= { oraEMNGEventEntry  8 }

oraEMNGEventOccurrenceTime  OBJECT-TYPE
    SYNTAX DisplayString
    ACCESS  read-only
    STATUS  mandatory
    DESCRIPTION
     "The time when this event occurred (optional), this is only populated for events that have occurrence time." 
    ::= { oraEMNGEventEntry  9 }

oraEMNGEventReportedTime  OBJECT-TYPE
    SYNTAX DisplayString
    ACCESS  read-only
    STATUS  mandatory
    DESCRIPTION
     "The time when this event was reported."
    ::= { oraEMNGEventEntry  10 }

oraEMNGEventCategories  OBJECT-TYPE
    SYNTAX DisplayString
    ACCESS  read-only
    STATUS  mandatory
    DESCRIPTION
     "The list of categories to which this event belongs to. Empty if trap size exceeds configured snmp packet size."
    ::= { oraEMNGEventEntry  11 }

oraEMNGEventCategoryCodes  OBJECT-TYPE
    SYNTAX DisplayString
    ACCESS  read-only
    STATUS  mandatory
    DESCRIPTION
     "The list of internal category codes to which this event belongs to. Empty if trap size exceeds configured snmp packet size."
    ::= { oraEMNGEventEntry  12 }

oraEMNGEventType  OBJECT-TYPE
    SYNTAX DisplayString
    ACCESS  read-only
    STATUS  mandatory
    DESCRIPTION
      "The name of the event type to which this event belongs to."
    ::= { oraEMNGEventEntry  13 }

oraEMNGEventName  OBJECT-TYPE
    SYNTAX DisplayString
    ACCESS  read-only
    STATUS  mandatory
    DESCRIPTION
      "The name of this event."
    ::= { oraEMNGEventEntry  14 }

oraEMNGAssocIncidentId  OBJECT-TYPE
    SYNTAX DisplayString
    ACCESS  read-only
    STATUS  mandatory
    DESCRIPTION
     "ID of the associated incident with the event (optional)."
    ::= { oraEMNGEventEntry  15 }

oraEMNGAssocIncidentOwner  OBJECT-TYPE
    SYNTAX DisplayString
    ACCESS  read-only
    STATUS  mandatory
    DESCRIPTION
     "Owner of the associated incident with the event (optional)."
    ::= { oraEMNGEventEntry  16 }

oraEMNGAssocIncidentAcked  OBJECT-TYPE
    SYNTAX DisplayString
    ACCESS  read-only
    STATUS  mandatory
    DESCRIPTION
     "Acknowledged status of the associated incident with the event. 1 indicates acknowledged, 0 indicates unacknowledged."
    ::= { oraEMNGEventEntry  17 }

oraEMNGAssocIncidentStatus  OBJECT-TYPE
    SYNTAX DisplayString
    ACCESS  read-only
    STATUS  mandatory
    DESCRIPTION
     "The status of the associated incident with the event."
    ::= { oraEMNGEventEntry  18 }

oraEMNGAssocIncidentPriority  OBJECT-TYPE
    SYNTAX DisplayString
    ACCESS  read-only
    STATUS  mandatory
    DESCRIPTION
     "The proirity of the associated incident with the event."
    ::= { oraEMNGEventEntry  19 }

oraEMNGAssocIncidentEscLevel  OBJECT-TYPE
    SYNTAX DisplayString
    ACCESS  read-only
    STATUS  mandatory
    DESCRIPTION
     "The Escalation Level of the associated incident with the event."
    ::= { oraEMNGEventEntry  20 }

oraEMNGEventTargetName  OBJECT-TYPE
    SYNTAX DisplayString
    ACCESS  read-only
    STATUS  mandatory
    DESCRIPTION
     "The name of the target to which this event applies. Populated for events that are about a target only."
    ::= { oraEMNGEventEntry  21 }

oraEMNGEventTargetNameURL  OBJECT-TYPE
    SYNTAX DisplayString
    ACCESS  read-only
    STATUS  mandatory
    DESCRIPTION
     "EM Console URL of the target to which this event applies. Populated for events that are about a target only. Empty if trap size exceeds configured snmp packet size."
    ::= { oraEMNGEventEntry  22 }

oraEMNGEventTargetType  OBJECT-TYPE
    SYNTAX DisplayString
    ACCESS  read-only
    STATUS  mandatory
    DESCRIPTION
     "The type of the target to which this event applies. Populated for events that are about a target only."
    ::= { oraEMNGEventEntry  23 }

oraEMNGEventHostName  OBJECT-TYPE
    SYNTAX DisplayString
    ACCESS  read-only
    STATUS  mandatory
    DESCRIPTION
     "The name of the host on which this event originated. Populated for events that are about a target only."
    ::= { oraEMNGEventEntry  24 }

oraEMNGEventTargetOwner  OBJECT-TYPE
    SYNTAX DisplayString
    ACCESS  read-only
    STATUS  mandatory
    DESCRIPTION
     "The primary administrator of the target on which this event originated. Empty if trap size exceeds configured snmp packet size."
    ::= { oraEMNGEventEntry  25 }

oraEMNGEventTgtLifeCycleStatus  OBJECT-TYPE
    SYNTAX DisplayString
    ACCESS  read-only
    STATUS  mandatory
    DESCRIPTION
     "The life cycle status of the target on which this event originated."
    ::= { oraEMNGEventEntry  26 }

oraEMNGEventTargetVersion  OBJECT-TYPE
    SYNTAX DisplayString
    ACCESS  read-only
    STATUS  mandatory
    DESCRIPTION
     "The version of the target on which this event originated."
    ::= { oraEMNGEventEntry  27 }

oraEMNGEventUserDefinedTgtProp  OBJECT-TYPE
    SYNTAX DisplayString
    ACCESS  read-only
    STATUS  mandatory
    DESCRIPTION
     "The user defined target properties [name,value pair list] of the associated target with this event. Empty if trap size exceeds configured snmp packet size."
    ::= { oraEMNGEventEntry  28 }

oraEMNGEventSourceObjName  OBJECT-TYPE
    SYNTAX DisplayString
    ACCESS  read-only
    STATUS  mandatory
    DESCRIPTION
     "The name of the source object to which this event belongs to. Populated for events that are about a non-target object only, such as Job."
    ::= { oraEMNGEventEntry  29 }

oraEMNGEventSourceObjNameURL  OBJECT-TYPE
    SYNTAX DisplayString
    ACCESS  read-only
    STATUS  mandatory
    DESCRIPTION
     "EM Console URL for the source object to which this event belongs to. Empty if trap size exceeds configured snmp packet size."
    ::= { oraEMNGEventEntry  30 }

oraEMNGEventSourceObjType  OBJECT-TYPE
    SYNTAX DisplayString
    ACCESS  read-only
    STATUS  mandatory
    DESCRIPTION
     "The type of the source object to which this event belongs to."
    ::= { oraEMNGEventEntry  31 }

oraEMNGEventSourceObjSubType  OBJECT-TYPE
    SYNTAX DisplayString
    ACCESS  read-only
    STATUS  mandatory
    DESCRIPTION
     "The sub type of the source object to which this event belongs to (Optional property). Empty if trap size exceeds configured snmp packet size."
    ::= { oraEMNGEventEntry  32 }

oraEMNGEventSourceObjOwner  OBJECT-TYPE
    SYNTAX DisplayString
    ACCESS  read-only
    STATUS  mandatory
    DESCRIPTION
     "The primary adminstrator of the source object to which this event belongs to. (Optional property). Empty if trap size exceeds configured snmp packet size."
    ::= { oraEMNGEventEntry  33 }

oraEMNGEventCAJobName  OBJECT-TYPE
    SYNTAX DisplayString
    ACCESS  read-only
    STATUS  mandatory
    DESCRIPTION
     "The Name of the Corrective Action Job associated with this event."
    ::= { oraEMNGEventEntry  34 }

oraEMNGEventCAJobStatus  OBJECT-TYPE
    SYNTAX DisplayString
    ACCESS  read-only
    STATUS  mandatory
    DESCRIPTION
     "The Status of the Corrective Action Job associated with this event."
    ::= { oraEMNGEventEntry  35 }

oraEMNGEventCAJobOwner  OBJECT-TYPE
    SYNTAX DisplayString
    ACCESS  read-only
    STATUS  mandatory
    DESCRIPTION
     "The Owner of the Corrective Action Job associated with this event."
    ::= { oraEMNGEventEntry  36 }

oraEMNGEventCAJobStepOutput  OBJECT-TYPE
    SYNTAX DisplayString
    ACCESS  read-only
    STATUS  mandatory
    DESCRIPTION
     "The job step output from the Corrective Action Job associated with this event."
    ::= { oraEMNGEventEntry  37 }

oraEMNGEventCAJobType  OBJECT-TYPE
    SYNTAX DisplayString
    ACCESS  read-only
    STATUS  mandatory
    DESCRIPTION
     "The job type from the Corrective Action Job associated with this event."
    ::= { oraEMNGEventEntry  38 }

oraEMNGEventRuleSetName  OBJECT-TYPE
    SYNTAX DisplayString
    ACCESS  read-only
    STATUS  mandatory
    DESCRIPTION
     "The name of the ruleset that caused this notification. Empty if trap size exceeds configured snmp packet size."
    ::= { oraEMNGEventEntry  39 }

oraEMNGEventRuleName  OBJECT-TYPE
    SYNTAX DisplayString
    ACCESS  read-only
    STATUS  mandatory
    DESCRIPTION
     "The name of the rule within the ruleset that caused this notification."
    ::= { oraEMNGEventEntry  40 }

oraEMNGEventRuleOwner  OBJECT-TYPE
    SYNTAX DisplayString
    ACCESS  read-only
    STATUS  mandatory
    DESCRIPTION
     "The owner of the ruleset that caused this notification."
    ::= { oraEMNGEventEntry  41 }

oraEMNGEventSequenceId  OBJECT-TYPE
    SYNTAX DisplayString
    ACCESS  read-only
    STATUS  mandatory
    DESCRIPTION
     "An EM generated identifier that uniquely identifies current issue until it is cleared."
    ::= { oraEMNGEventEntry  42 }

oraEMNGEventRCADetails  OBJECT-TYPE
    SYNTAX DisplayString
    ACCESS  read-only
    STATUS  mandatory
    DESCRIPTION
     "Root Cause Analysis details associated with this event if it exists."
    ::= { oraEMNGEventEntry  43 }

oraEMNGEventContextAttrs  OBJECT-TYPE
    SYNTAX DisplayString
    ACCESS  read-only
    STATUS  mandatory
    DESCRIPTION
     "The context attributes associated with this event. Empty if trap size exceeds configured snmp packet size."
    ::= { oraEMNGEventEntry  44 }

oraEMNGEventUserComments  OBJECT-TYPE
    SYNTAX DisplayString
    ACCESS  read-only
    STATUS  mandatory
    DESCRIPTION
     "The user comments associated with this event. Empty if trap size exceeds configured snmp packet size."
    ::= { oraEMNGEventEntry  45 }

oraEMNGEventUpdates  OBJECT-TYPE
    SYNTAX DisplayString
    ACCESS  read-only
    STATUS  mandatory
    DESCRIPTION
     "The updates associated with this event. Empty if trap size exceeds configured snmp packet size."
    ::= { oraEMNGEventEntry  46 }

oraEMNGEventTotalOccurrenceCount  OBJECT-TYPE
    SYNTAX DisplayString
    ACCESS  read-only
    STATUS  mandatory
    DESCRIPTION
     "Total number of occurrences of the same event on a target across all open deduplicated events. This attribute applies only to deduplicated events."
    ::= { oraEMNGEventEntry  47 }

oraEMNGEventCurrOccurrenceCount  OBJECT-TYPE
    SYNTAX DisplayString
    ACCESS  read-only
    STATUS  mandatory
    DESCRIPTION
     "Total occurrences of the event in this collection period. This attribute applies only to deduplicated events."
    ::= { oraEMNGEventEntry  48 }

oraEMNGEventCurrFirstOccurDate  OBJECT-TYPE
    SYNTAX DisplayString
    ACCESS  read-only
    STATUS  mandatory
    DESCRIPTION
     "Timestamp when the event first occurred in this collection period. This attribute applies only to deduplicated events."
    ::= { oraEMNGEventEntry  49 }

oraEMNGEventCurrLastOccurDate  OBJECT-TYPE
    SYNTAX DisplayString
    ACCESS  read-only
    STATUS  mandatory
    DESCRIPTION
     "Timestamp when the event last occurred in this collection period. This attribute applies only to deduplicated events."
    ::= { oraEMNGEventEntry  50 }

oraEMNGEventRCAStatus  OBJECT-TYPE
    SYNTAX DisplayString
    ACCESS  read-only
    STATUS  mandatory
    DESCRIPTION
     "Summary of Root Cause Analysis, if applicable."
    ::= { oraEMNGEventEntry  51 }

oraEMNGEventReportedState  OBJECT-TYPE
    SYNTAX DisplayString
    ACCESS  read-only
    STATUS  mandatory
    DESCRIPTION
     "This is an optional value reporting the latest state of an entity and is only applicable for events that are representing a state transition for a given entity. For example, for Target availability and Job state change events, this value would be the latest state of the target or job, respectively."
    ::= { oraEMNGEventEntry  52 }

oraEMNGEventTypeAttr1  OBJECT-TYPE
    SYNTAX DisplayString
    ACCESS  read-only
    STATUS  mandatory
    DESCRIPTION
     "Name and value pair as name=value for event type specific attribute#1."
    ::= { oraEMNGEventEntry  61 }

oraEMNGEventTypeAttr2  OBJECT-TYPE
    SYNTAX DisplayString
    ACCESS  read-only
    STATUS  mandatory
    DESCRIPTION
     "Name and value pair as name=value for event type specific attribute#2."
    ::= { oraEMNGEventEntry  62 }

oraEMNGEventTypeAttr3  OBJECT-TYPE
    SYNTAX DisplayString
    ACCESS  read-only
    STATUS  mandatory
    DESCRIPTION
     "Name and value pair as name=value for event type specific attribute#3."
    ::= { oraEMNGEventEntry  63 }

oraEMNGEventTypeAttr4  OBJECT-TYPE
    SYNTAX DisplayString
    ACCESS  read-only
    STATUS  mandatory
    DESCRIPTION
     "Name and value pair as name=value for event type specific attribute#4."
    ::= { oraEMNGEventEntry  64 }

oraEMNGEventTypeAttr5  OBJECT-TYPE
    SYNTAX DisplayString
    ACCESS  read-only
    STATUS  mandatory
    DESCRIPTION
     "Name and value pair as name=value for event type specific attribute#5."
    ::= { oraEMNGEventEntry  65 }

oraEMNGEventTypeAttr6  OBJECT-TYPE
    SYNTAX DisplayString
    ACCESS  read-only
    STATUS  mandatory
    DESCRIPTION
     "Name and value pair as name=value for event type specific attribute#6."
    ::= { oraEMNGEventEntry  66 }

oraEMNGEventTypeAttr7  OBJECT-TYPE
    SYNTAX DisplayString
    ACCESS  read-only
    STATUS  mandatory
    DESCRIPTION
     "Name and value pair as name=value for event type specific attribute#7."
    ::= { oraEMNGEventEntry  67 }

oraEMNGEventTypeAttr8  OBJECT-TYPE
    SYNTAX DisplayString
    ACCESS  read-only
    STATUS  mandatory
    DESCRIPTION
     "Name and value pair as name=value for event type specific attribute#8."
    ::= { oraEMNGEventEntry  68 }

oraEMNGEventTypeAttr9  OBJECT-TYPE
    SYNTAX DisplayString
    ACCESS  read-only
    STATUS  mandatory
    DESCRIPTION
     "Name and value pair as name=value for event type specific attribute#9."
    ::= { oraEMNGEventEntry  69 }

oraEMNGEventTypeAttr10  OBJECT-TYPE
    SYNTAX DisplayString
    ACCESS  read-only
    STATUS  mandatory
    DESCRIPTION
     "Name and value pair as name=value for event type specific attribute#10."
    ::= { oraEMNGEventEntry  70 }

oraEMNGEventTypeAttr11  OBJECT-TYPE
    SYNTAX DisplayString
    ACCESS  read-only
    STATUS  mandatory
    DESCRIPTION
     "Name and value pair as name=value for event type specific attribute#11."
    ::= { oraEMNGEventEntry  71 }

oraEMNGEventTypeAttr12  OBJECT-TYPE
    SYNTAX DisplayString
    ACCESS  read-only
    STATUS  mandatory
    DESCRIPTION
     "Name and value pair as name=value for event type specific attribute#12."
    ::= { oraEMNGEventEntry  72 }

oraEMNGEventTypeAttr13  OBJECT-TYPE
    SYNTAX DisplayString
    ACCESS  read-only
    STATUS  mandatory
    DESCRIPTION
     "Name and value pair as name=value for event type specific attribute#13."
    ::= { oraEMNGEventEntry  73 }

oraEMNGEventTypeAttr14  OBJECT-TYPE
    SYNTAX DisplayString
    ACCESS  read-only
    STATUS  mandatory
    DESCRIPTION
     "Name and value pair as name=value for event type specific attribute#14."
    ::= { oraEMNGEventEntry  74 }

oraEMNGEventTypeAttr15  OBJECT-TYPE
    SYNTAX DisplayString
    ACCESS  read-only
    STATUS  mandatory
    DESCRIPTION
     "Name and value pair as name=value for event type specific attribute#15."
    ::= { oraEMNGEventEntry  75 }

oraEMNGEventTypeAttr16  OBJECT-TYPE
    SYNTAX DisplayString
    ACCESS  read-only
    STATUS  mandatory
    DESCRIPTION
     "Name and value pair as name=value for event type specific attribute#16."
    ::= { oraEMNGEventEntry  76 }

oraEMNGEventTypeAttr17  OBJECT-TYPE
    SYNTAX DisplayString
    ACCESS  read-only
    STATUS  mandatory
    DESCRIPTION
     "Name and value pair as name=value for event type specific attribute#17."
    ::= { oraEMNGEventEntry  77 }

oraEMNGEventTypeAttr18  OBJECT-TYPE
    SYNTAX DisplayString
    ACCESS  read-only
    STATUS  mandatory
    DESCRIPTION
     "Name and value pair as name=value for event type specific attribute#18."
    ::= { oraEMNGEventEntry  78 }

oraEMNGEventTypeAttr19  OBJECT-TYPE
    SYNTAX DisplayString
    ACCESS  read-only
    STATUS  mandatory
    DESCRIPTION
     "Name and value pair as name=value for event type specific attribute#19."
    ::= { oraEMNGEventEntry  79 }

oraEMNGEventTypeAttr20  OBJECT-TYPE
    SYNTAX DisplayString
    ACCESS  read-only
    STATUS  mandatory
    DESCRIPTION
     "Name and value pair as name=value for event type specific attribute#20."
    ::= { oraEMNGEventEntry  80 }

oraEMNGEventTypeAttr21  OBJECT-TYPE
    SYNTAX DisplayString
    ACCESS  read-only
    STATUS  mandatory
    DESCRIPTION
     "Name and value pair as name=value for event type specific attribute#21."
    ::= { oraEMNGEventEntry  81 }

oraEMNGEventTypeAttr22  OBJECT-TYPE
    SYNTAX DisplayString
    ACCESS  read-only
    STATUS  mandatory
    DESCRIPTION
     "Name and value pair as name=value for event type specific attribute#22."
    ::= { oraEMNGEventEntry  82 }

oraEMNGEventTypeAttr23  OBJECT-TYPE
    SYNTAX DisplayString
    ACCESS  read-only
    STATUS  mandatory
    DESCRIPTION
     "Name and value pair as name=value for event type specific attribute#23."
    ::= { oraEMNGEventEntry  83 }

oraEMNGEventTypeAttr24  OBJECT-TYPE
    SYNTAX DisplayString
    ACCESS  read-only
    STATUS  mandatory
    DESCRIPTION
     "Name and value pair as name=value for event type specific attribute#24."
    ::= { oraEMNGEventEntry  84 }

oraEMNGEventTypeAttr25  OBJECT-TYPE
    SYNTAX DisplayString
    ACCESS  read-only
    STATUS  mandatory
    DESCRIPTION
     "Name and value pair as name=value for event type specific attribute#25."
    ::= { oraEMNGEventEntry  85 }

oraEMNGEvent TRAP-TYPE
    ENTERPRISE  oraEM4Traps
    VARIABLES   {
          oraEMNGEventNotifType,
          oraEMNGEventMessage, oraEMNGEventMessageURL,
          oraEMNGEventSeverity, oraEMNGEventSeverityCode, 
          oraEMNGEventRepeatCount, oraEMNGEventActionMsg,
          oraEMNGEventOccurrenceTime, oraEMNGEventReportedTime,
          oraEMNGEventCategories, oraEMNGEventCategoryCodes,
          oraEMNGEventType, oraEMNGEventName,
          oraEMNGAssocIncidentId, oraEMNGAssocIncidentOwner,
          oraEMNGAssocIncidentAcked, oraEMNGAssocIncidentStatus,
          oraEMNGAssocIncidentPriority, oraEMNGAssocIncidentEscLevel,
          oraEMNGEventTargetName, oraEMNGEventTargetNameURL,
          oraEMNGEventTargetType, oraEMNGEventHostName,
          oraEMNGEventTargetOwner, oraEMNGEventTgtLifeCycleStatus,
          oraEMNGEventTargetVersion, oraEMNGEventUserDefinedTgtProp,
          oraEMNGEventSourceObjName, oraEMNGEventSourceObjNameURL,
          oraEMNGEventSourceObjType, oraEMNGEventSourceObjSubType,
          oraEMNGEventSourceObjOwner, oraEMNGEventCAJobName,
          oraEMNGEventCAJobStatus, oraEMNGEventCAJobOwner,
          oraEMNGEventCAJobStepOutput, oraEMNGEventCAJobType,
          oraEMNGEventRuleSetName, oraEMNGEventRuleName,
          oraEMNGEventRuleOwner, oraEMNGEventSequenceId,
          oraEMNGEventRCADetails, oraEMNGEventContextAttrs,
          oraEMNGEventUserComments, oraEMNGEventUpdates,
          oraEMNGEventTotalOccurrenceCount, oraEMNGEventCurrOccurrenceCount,
          oraEMNGEventCurrFirstOccurDate, oraEMNGEventCurrLastOccurDate,
          oraEMNGEventRCAStatus,
          oraEMNGEventTypeAttr1, oraEMNGEventTypeAttr2,
          oraEMNGEventTypeAttr3, oraEMNGEventTypeAttr4,
          oraEMNGEventTypeAttr5, oraEMNGEventTypeAttr6,
          oraEMNGEventTypeAttr7, oraEMNGEventTypeAttr8,
          oraEMNGEventTypeAttr9, oraEMNGEventTypeAttr10,
          oraEMNGEventTypeAttr11, oraEMNGEventTypeAttr12,
          oraEMNGEventTypeAttr13, oraEMNGEventTypeAttr14,
          oraEMNGEventTypeAttr15, oraEMNGEventTypeAttr16,
          oraEMNGEventTypeAttr17, oraEMNGEventTypeAttr18,
          oraEMNGEventTypeAttr19, oraEMNGEventTypeAttr20,
          oraEMNGEventTypeAttr21, oraEMNGEventTypeAttr22,
          oraEMNGEventTypeAttr23, oraEMNGEventTypeAttr24,
          oraEMNGEventTypeAttr25,
          oraEMNGEventReportedState
}
    DESCRIPTION
     "The variables included in the oraEMNGAlert trap."
    ::= 3

END
